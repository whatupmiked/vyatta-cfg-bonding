module vyatta-lacp-v1 {
    namespace "urn:vyatta.com:mgmt:vyatta-lacp:1";
    prefix vyatta-lacp-v1;

    import vyatta-lacp-types-v1 {
        prefix lacp;
    }

    import configd-v1 {
        prefix configd;
    }

    import vyatta-types-v1 {
        prefix types;
    }

    import vyatta-interfaces-v1 {
        prefix if;
    }

    import vyatta-system-v1 {
        prefix sys;
    }

    description
        "
        This program is free software; you can redistribute it and/or modify
        it under the terms of the GNU General Public License version 2 as
        published by the Free Software Foundation.

        This program is distributed in the hope that it will be useful, but
        WITHOUT ANY WARRANTY; without even the implied warranty of
        MERCHANTABILITY or FITNESS FOR A PARTICULAR PURPOSE.  See the GNU
        General Public License for more details.

        Date: March 2020

        SPDX-License-Identifier: GPL-2.0-only

        The YANG module for vyatta-lacp-v1.
        This module provides configd infrastructure for lacp state";

    revision 2020-03-26 {
        description "Initial revision";
    }

    augment /if:interfaces {
        container lacp-lags-state {
            config false;
            configd:get-state "/opt/vyatta/bin/lacp-state -j";
            description "Operational state for LACP lags";

            list lags {
                key name;
                leaf name {
                    description "Interface name associated with LACP link aggregation group";
                    type types:interface-ifname;
                }
                uses lacp-lag-state;
            }
        }
    }

    grouping lacp-lag-state {
        leaf ether {
            type types:mac-address;
            description "";
        }

        leaf mtu {
            type string;
            description "";
        }

        leaf speed {
            type string;
            description "";
        }

        leaf duplex {
            type string;
            description "";
        }

        leaf up {
            type boolean;
            description "";
        }

        leaf age {
            type string;
            description "";
        }

        leaf rx_packets {
            type if:packets;
            description "";
        }

        leaf rx_errors {
            type if:packets;
            description "";
        }

        leaf rx_dropped {
            type if:packets;
            description "";
        }

        leaf tx_packets {
            type if:packets;
            description "";
        }

        leaf tx_errors {
            type if:packets;
            description "";
        }

        leaf tx_dropped {
            type if:packets;
            description "";
        }

        leaf mode {
            description "";
            type string;
        }

        leaf fast_rate {
            description "The LACPDU rate timer advertised to partner";
            type string;
        }

        leaf lacp {
            description "Is LACP running on this lag";
            type boolean;
        }

        leaf hash_alg {
            description "The hashing algorithm used by the dataplane for this lag";
            type string;
        }

        leaf active {
            description "";
            type boolean;
        }

        leaf team_mode {
            description "The teamd team-mode for this lag";
            type string;
        }

        leaf controller {
            description "The teamd controller used for this lag";
            type string;
        }

        leaf link_watch {
            description "The teamd link_watch type used for this lag";
            type string;
        }

        leaf-list tx_hash {
            type string;
            description "";
        }

        leaf sys_prio {
            type lacp:system-priority;
            description "";
        }

        list slaves {
            description "";
            key name;
            leaf name {
                description "Interface name associated with LACP link aggregation group";
                type types:interface-ifname;
            }
            uses lacp-port-state;
        }
    }

    grouping lacp-port-state {
        leaf dp_master {
            type types:interface-ifname;
            description "";
        }

        leaf version {
            type lacp:lacp-version;
            description "";
        }

        leaf dp_lacp {
            description "Is LACP running on this lag";
            type boolean;
        }

        leaf dp_active {
            type boolean;
            description "";
        }

        leaf dp_primary {
            type boolean;
            description "";
        }

        leaf prio {
            type lacp:port-priority;
            description "";
        }

        leaf actor_sys_prio {
            type lacp:actor-priority;
            description "";
        }

        leaf actor_sys_id {
            type lacp:actor-system-id;
            description "";
        }

        leaf actor_key {
            type lacp:actor-key;
            description "";
        }

        leaf actor_port_prio {
            type lacp:actor-port-priority;
            description "";
        }

        leaf actor_port_id {
            type lacp:actor-port-id;
            description "";
        }

        leaf actor_state {
            type lacp:actor-state;
            description "";
        }

        leaf dp_actor_state {
            type lacp:actor-state;
            description "";
        }

        leaf partner_sys_prio {
            type lacp:partner-system-priority;
            description "";
        }

        leaf partner_sys_id {
            type lacp:partner-system-id;
            description "";
        }

        leaf partner_key {
            type lacp:partner-key;
            description "";
        }

        leaf partner_port_prio {
            type lacp:partner-port-priority;
            description "";
        }

        leaf partner_port_id {
            type lacp:partner-port-id;
            description "";
        }

        leaf partner_state {
            type lacp:partner-state;
            description "";
        }

        leaf dp_partner_state {
            type lacp:partner-state;
            description "";
        }

        leaf ether {
            type types:mac-address;
            description "";
        }

        leaf mtu {
            type string;
            description "";
        }

        leaf up {
            type boolean;
            description "";
        }

        leaf speed {
            type string;
            description "";
        }

        leaf age {
            type string;
            description "";
        }

        leaf duplex {
            type string;
            description "";
        }

        leaf rx_packets {
            type if:packets;
            description "";
        }

        leaf rx_errors {
            type if:packets;
            description "";
        }

        leaf rx_dropped {
            type if:packets;
            description "";
        }

        leaf tx_packets {
            type if:packets;
            description "";
        }

        leaf tx_errors {
            type if:packets;
            description "";
        }

        leaf tx_dropped {
            type if:packets;
            description "";
        }
    }
}
